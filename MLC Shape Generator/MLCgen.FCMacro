# -*- coding: utf-8 -*-

###############################################################################################################################
###############################################################################################################################
##                                                                                                                           ##
##  MLC Shape Generator for SKINCOILS                                                                                        ##
##                                                                                                                           ##
##  Copyright (c) 2025:                                                                                                      ##
##  Andreas Reich-Rohrwig,                                                                                                   ##
##  Center for Medical Physics and Biomedical Engineering,                                                                   ##
##  Medical University of Vienna                                                                                             ##
##                                                                                                                           ##
##                                                                                                                           ##
##  Permission is granted to use, copy, modify, and distribute this software                                                 ##
##  for academic and research purposes, provided that the above copyright                                                    ##
##  notice and this permission notice appear in all copies and that proper                                                   ##
##  acknowledgment is given in any publications or presentations based on                                                    ##
##  this work.                                                                                                               ##
##                                                                                                                           ##
##                                                                                                                           ##
##  THE SOFTWARE IS PROVIDED "AS IS", WITHOUT WARRANTY OF ANY KIND,                                                          ##
##  EXPRESS OR IMPLIED, INCLUDING BUT NOT LIMITED TO THE WARRANTIES OF                                                       ##
##  MERCHANTABILITY, FITNESS FOR A PARTICULAR PURPOSE AND NONINFRINGEMENT.                                                   ##
##  IN NO EVENT SHALL THE AUTHORS OR COPYRIGHT HOLDERS BE LIABLE FOR ANY                                                     ##
##  CLAIM, DAMAGES, OR OTHER LIABILITY, WHETHER IN AN ACTION OF CONTRACT,                                                    ##
##  TORT OR OTHERWISE, ARISING FROM, OUT OF OR IN CONNECTION WITH THE                                                        ##
##  SOFTWARE OR THE USE OR OTHER DEALINGS IN THE SOFTWARE.                                                                   ##
##                                                                                                                           ##
##                                                                                                                           ##
##  For other uses (including commercial), please contact Roberta Frass-Kriegl:                                              ##
##  roberta.frass@meduniwien.ac.at                                                                                           ##
##                                                                                                                           ##
###############################################################################################################################
###############################################################################################################################


import FreeCAD, Draft; from math import *
def cosD(angle): return cos(angle*pi/180)
def sinD(angle): return sin(angle*pi/180)

# User parameters #############################################################################################################
mm, cm, m, um, degrees     = 1, 10, 1000, 1/1000, 1
layerOffset                = 400*um
X0, Y0, ThetaD0            = 0*mm, 0*mm, 0*degrees
Z0                         = 0*layerOffset
distanceBetweenConductors  = 0.5*mm
conductorWidth             = 1.5*mm
overlap                    = 0.775
gapSize                    = 4*mm
arcSampleNumber            = 300
relativeSampling           = True
flagConstantWidth          = True
logging                    = False

if(flagConstantWidth):
	totalLength            = 79*mm
	loopRadius             = totalLength/(4*overlap*sqrt(3)+2)
	distanceBetweenCenters = totalLength/2-loopRadius
else: #variable width of the MLC
	loopRadius             = 11.5*mm
	totalLength            = loopRadius*(4*overlap*sqrt(3)+2)
	distanceBetweenCenters = totalLength/2-loopRadius

try:    lengthOfConnectionLine = distanceBetweenCenters - 2*loopRadius
except: distanceBetweenCenters = 2*loopRadius + lengthOfConnectionLine

# Shapes see further below

# Classes #####################################################################################################################
class ConductorElement:
	def __init__(self, type="none", linelength=1, lineangle=0, arcRx = 1, arcRy = 0, arcsamples=100, arcangleD=180):
		self.type       = type
		self.linelength = linelength
		self.lineangle  = lineangle
		self.arcRx      = arcRx
		self.arcRy      = arcRy
		self.arcsamples = arcsamples
		self.arcangleD  = arcangleD

# Functions ###################################################################################################################
def getAngleDFromABR(Ax,Ay,Bx,By,Rx,Ry): return (atan2(By-Ry, Bx-Rx)-atan2(Ay-Ry, Ax-Rx))*180/pi

def log(*arg): #---------------------------------------------------------------------------------------------------------------
	if(logging==True): print("LOG:", *arg)

def locate(X,Y): #-------------------------------------------------------------------------------------------------------------
	placePoint(X+0.001,Y+0); placePoint(X+0.001,Y+0.001); placePoint(X+0,Y+0.001)

def turn(angleD): #------------------------------------------------------------------------------------------------------------
	global ThetaD
	ThetaD = (ThetaD+angleD)%360

''' <- toggle comment here to switch between XY and XZ (add/remove # at the start of the line)
def placePoint(X,Y): #Place the shapes in a XY plane #-------------------------------------------------------------------------
	global Z0
	points.append(FreeCAD.Vector(X, Y, Z0))
'''
def placePoint(X,Z): #Place the shapes in a XZ plane #-------------------------------------------------------------------------
	global Z0
	points.append(FreeCAD.Vector(X, Z0, Z))
#'''

def drawPointAtAngle(Rx, Ry, angleD): #----------------------------------------------------------------------------------------
	global Ax, Ay
	Xtemp, Ytemp = Ax-Rx, Ay-Ry
	Ax, Ay       = Rx + Xtemp*cos(angleD*pi/180) - Ytemp*sin(angleD*pi/180), Ry + Xtemp*sin(angleD*pi/180) + Ytemp*cos(angleD*pi/180)
	placePoint(Ax, Ay)

#still old = not tested
def drawArc(OI, Rx, Ry, samples, angleD, offset=0, overlength=0, gapOffsetA=0, gapOffsetB=0):
	global X,Y, Ax, Ay, ThetaD, currentRx, currentRy
	currentRx, currentRy = Rx,   Ry
	if OI == "O": Ax, Ay = X+overlength*cosD(ThetaD)+(offset+gapOffsetA)*sinD(ThetaD), Y+overlength*sinD(ThetaD)-(offset+gapOffsetA)*cosD(ThetaD)
	ThetaD               = ThetaD+angleD-180
	Xtemp,Ytemp          = X-Rx, Y-Ry
	X                    = Rx+Xtemp*cosD(angleD)-Ytemp*sinD(angleD)
	Y                    = Ry+Xtemp*sinD(angleD)+Ytemp*cosD(angleD)
	Bx                   = X-overlength*cosD(ThetaD)+(offset+gapOffsetB)*sinD(ThetaD)
	By                   = Y-overlength*sinD(ThetaD)-(offset+gapOffsetB)*cosD(ThetaD)
	tempD                = getAngleDFromABR(Ax,Ay,Bx,By,Rx,Ry)
	if   angleD-tempD > 180 : angleD = tempD+360
	elif angleD-tempD < -180: angleD = tempD-360
	else:                     angleD = tempD
	for i in range(0,samples): drawPointAtAngle(Rx, Ry, angleD/samples)

def drawLine(length, angleD, offset=0, overlength=0): #------------------------------------------------------------------------
	global X, Y, Ax, Ay, ThetaD
	ThetaD  = ThetaD + angleD
	Ax      = X + cosD(ThetaD)*length + overlength*cosD(ThetaD) + offset*sinD(ThetaD)
	Ay      = Y + sinD(ThetaD)*length + overlength*sinD(ThetaD) - offset*cosD(ThetaD)
	X, Y    = X + cosD(ThetaD)*length, Y + sinD(ThetaD)*length
	placePoint(Ax, Ay)

def turnaroundLine(length): #--------------------------------------------------------------------------------------------------
	global Ax, Ay, X, Y, ThetaD, currentRx, currentRy
	ThetaD          = ThetaD-90
	angleAXR        = getAngleDFromABR(Ax,Ay,X,Y,currentRx,currentRy)
	correctedLength = sqrt((loopRadius+length)**2+loopRadius**2*cosD(angleAXR)**2-loopRadius**2)-loopRadius*cosD(angleAXR)
	X,Y             = X + sinD(ThetaD)*length, Y - cosD(ThetaD)*length
	Ax, Ay          = Ax + sinD(ThetaD)*correctedLength, Ay-cosD(ThetaD)*correctedLength
	placePoint(Ax,Ay)
	turn(90)

def drawConductorPartOuter(self): #--------------------------------------------------------------------------------------------
	if   self.type == "line":    drawLine(self.linelength, self.lineangle, offsetO, overlengthO)
	elif self.type == "arc" :
		if elementNr == 0:       drawArc("O", self.arcRx, self.arcRy, self.arcsamples, self.arcangleD, offsetO, overlengthStart, gapSize/2-offsetO, 0)
		elif elementNr == elMax: drawArc("O", self.arcRx, self.arcRy, self.arcsamples, self.arcangleD, offsetO, overlengthO    , 0                , gapSize/2-offsetO)
		else:                    drawArc("O", self.arcRx, self.arcRy, self.arcsamples, self.arcangleD, offsetO, overlengthO    , 0                , 0)

def drawConductorPartInner(self): #--------------------------------------------------------------------------------------------
	if   self.type == "line":    drawLine(self.linelength+2*conductorWidth,-self.lineangle, offsetI, overlengthI)
	elif self.type == "arc":
		if elementNr == 0:       drawArc("I", self.arcRx, self.arcRy, self.arcsamples,-self.arcangleD, offsetI, overlengthStart , 0, -gapSize/2-offsetI)
		else:                    drawArc("I", self.arcRx, self.arcRy, self.arcsamples,-self.arcangleD, offsetI, overlengthI     , 0, 0                 )

def drawConductorRecursively(todoList):#---------------------------------------------------------------------------------------
	global elementNr, nextX0, nextY0, nextThetaD0
	self = todoList.pop(0)
	drawConductorPartOuter(self)
	elementNr = elementNr + 1
	if todoList == []:#then turn around
		if self.type == "arc":  turn(180)
		nextX0, nextY0, nextThetaD0 = X,Y,ThetaD
		turnaroundLine(-conductorWidth)
	else:
		drawConductorRecursively(todoList)
	elementNr = elementNr - 1
	drawConductorPartInner(self)

def init(): #------------------------------------------------------------------------------------------------------------------
	global points, todoList, X, Y, ThetaD, Ax, Ay, elementNr, elMax, listAngles, listRx, listRy, currentRx, currentRy, offsetO, offsetI, overlengthO, overlengthI, overlengthStart, overlengthEnd, numberOfShapes
	points, todoList     = [], []
	X,  Y,  ThetaD       = X0, Y0, ThetaD0
	Ax, Ay               = X,  Y
	elementNr, elMax     = 0,  0
	listAngles           = []
	listRx, listRy       = [], []
	currentRx, currentRy = 0,  0
	offsetO              = distanceBetweenConductors/2 + conductorWidth
	offsetI              =-distanceBetweenConductors/2
	overlengthO          = loopRadius                - sqrt( loopRadius**2                -offsetO**2    )
	overlengthI          = loopRadius-conductorWidth - sqrt((loopRadius-conductorWidth)**2-offsetI**2    )
	overlengthStart      = loopRadius                - sqrt( loopRadius**2                -(gapSize/2)**2)
	overlengthEnd        = loopRadius-conductorWidth - sqrt((loopRadius-conductorWidth)**2-(gapSize/2)**2)
	numberOfShapes       = len(MLCshape)

def drawWholeConductor(): #----------------------------------------------------------------------------------------------------
	global points, todoList, X, Y, ThetaD, Ax, Ay, elementNr, elMax, listAngles, listRx, listRy, currentRx, currentRy, offsetO, offsetI, overlengthO, overlengthI, overlengthStart, overlengthEnd, numberOfShapes, ThetaD0, X0, Y0, Z0
	print("LOG: START")
	init()
	
	shapeCounter = 0
	while (shapeCounter < numberOfShapes):
	
		shapeCounter = shapeCounter+1
		log("current shape nr: ", shapeCounter)
		if shapeCounter != 1: X0, Y0, ThetaD0 = round(nextX0,10), round(nextY0,10), round(nextThetaD0,10)
	
		log("initializing...")
		listAnglesBase = MLCshape[shapeCounter-1]
		init()
	
		log("preparing angles...")
		numberOfLoops  = len(listAnglesBase)
		for i in range(0,numberOfLoops+1):
			listAngles.append(ThetaD0)
			for j in range(0,i): listAngles[i] = listAngles[i] + listAnglesBase[j]
		listAngles.pop(0)
	
		log("preparing list of center points...")
		listRx.append( X0+loopRadius*cos(ThetaD*pi/180) ); listRy.append( Y0+loopRadius*sin(ThetaD*pi/180) )
		for i in range(0,numberOfLoops):
			listRx.append( listRx[i]+((-1)**i)*distanceBetweenCenters*cos(listAngles[i]*pi/180+pi) )
			listRy.append( listRy[i]+((-1)**i)*distanceBetweenCenters*sin(listAngles[i]*pi/180+pi) )
	
		log("drawing wire...")
		arcsamples = arcSampleNumber
		if relativeSampling==True: arcsamples = int(round(arcSampleNumber*listAnglesBase[0]/360,0))
		todoList.append(ConductorElement(type="arc", arcRx=listRx[0], arcRy=listRy[0], arcangleD = listAnglesBase[0], arcsamples = arcsamples))
		for i in range(1,numberOfLoops):
			todoList.append(ConductorElement(type="line", linelength=lengthOfConnectionLine))
			arcsamples = arcSampleNumber
			if relativeSampling==True: arcsamples = int(round(arcSampleNumber*listAnglesBase[i]/360,0))
			todoList.append(ConductorElement(type="arc", arcRx=listRx[i], arcRy=listRy[i], arcangleD = listAnglesBase[i], arcsamples = arcsamples))
	
		log("drawing macro...")
		elMax    = len(todoList) - 1
		Ax            = X0 + overlengthStart*cosD(ThetaD) + (gapSize/2)*sinD(ThetaD)
		Ay            = Y0 + overlengthStart*sinD(ThetaD) - (gapSize/2)*cosD(ThetaD)
		placePoint(Ax, Ay)
		drawConductorRecursively(todoList)
	
		pl = FreeCAD.Placement(); pl.Rotation.Q = (0.0, 0.0, 0.0, 1.0); pl.Base = FreeCAD.Vector(1, 1, 0.0); line = Draft.make_wire(points, placement=pl, closed=True, face=True, support=None); Draft.autogroup(line); FreeCAD.ActiveDocument.recompute()
		log("wire drawn successfully\n")
	
	print("LOG: END \n--------------")

# RUN the macro individually for each shape ####################################################################################

# ------------------------------------------------------------------------------------------------------------------------------
X0, Y0, Z0, ThetaD0 = -totalLength/2, 0, 2*layerOffset, 0
MLCshape = [ #hexagon TOP
	[120,240,150],
	[150,180,30] ,
	[30,120,240] ,
	[120,240,150],
	[150,180,30] ,
	[30,120,240] ]
drawWholeConductor()
# ------------------------------------------------------------------------------------------------------------------------------
X0, Y0, Z0, ThetaD0 = -totalLength/2, +distanceBetweenCenters/sqrt(3), 1*layerOffset, 0
MLCshape = [ #Triangle MID
	[120,180,120] ,
	[180,150]     ,
	[90,60,180]   ,
	[180,210]     ,
	[90,120,60,30],
	[150,240]     ]
drawWholeConductor()
# ------------------------------------------------------------------------------------------------------------------------------
X0, Y0, Z0, ThetaD0 = -totalLength/2, -distanceBetweenCenters/sqrt(3), 0*layerOffset, 0
MLCshape = [ #Triangle BOT
	[180,210]     ,
	[90,120,60,30],
	[150,240]     ,
	[120,180,120] ,
	[180,150]     ,
	[90,60,180]   ]
drawWholeConductor()
# ------------------------------------------------------------------------------------------------------------------------------
